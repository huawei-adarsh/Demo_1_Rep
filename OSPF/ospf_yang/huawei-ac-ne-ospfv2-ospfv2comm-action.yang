/*
WARNING:
This yang model is just for fuction ONOS opensource project demo purpose only,
And is subject to change in future, Huawei does not commit provide compatibilty
in commercial product.
*/
submodule huawei-ac-ne-ospfv2-ospfv2comm-action {
	belongs-to "huawei-ac-ne-ospfv2"{
		prefix ospfv2;
	}
	organization "Huawei Technologies Co., Ltd";
	contact 
	"Huawei Industrial Base
	 Bantian, Longgang
	 Shenzhen 518129
	 People's Republic of China
	 Website: http://www.huawei.com
	 Email: support@huawei.com
	";
	description "ac-ne-ospfv2-ospfv2comm-action yang";
	revision "2014-12-25" {
		reference "ac-ne-ospfv2-ospfv2comm-action yang";
	}
/*
	rpc ospfv2comm-resetRedistribution {
		description "";
		input {
			leaf ne-id {
				type leafref {                
					path "/inv:inventory-cfg/inv:nes/inv:ne/inv:id";
				}
				description "Node id";
		    }
			leaf processId {
				type "uint32";
				description "";
			}
		}
	}
	rpc ospfv2comm-resetCounter {
		description "";
		input {
			leaf ne-id {
				type leafref {                
					path "/inv:inventory-cfg/inv:nes/inv:ne/inv:id";
				}
				description "Node id";
		    }
			leaf processId {
				type "uint32";
				description "";
			}
			leaf routerId {
				type "pub-type:ipv4Address";
				description "";
			}
			leaf ifName {
				type "pub-type:ifName";
				description "";
			}
		}
	}
	rpc ospfv2comm-resetProcess {
		description "";
		input {
			leaf ne-id {
				type leafref {                
					path "/inv:inventory-cfg/inv:nes/inv:ne/inv:id";
				}
				description "Node id";
		    }
			leaf processId {
				type "uint32";
				description "";
			}
		}
	}
	rpc ospfv2comm-resetPeer {
		description "";
		input {
			leaf ne-id {
				type leafref {                
					path "/inv:inventory-cfg/inv:nes/inv:ne/inv:id";
				}
				description "Node id";
		    }
			leaf processId {
				type "uint32";
				description "";
			}
			leaf routerId {
				type "pub-type:ipv4Address";
				description "";
			}
			leaf ifName {
				type "pub-type:ifName";
				description "";
			}
		}
	}
	rpc ospfv2comm-resetSpf {
		description "";
		input {
			leaf ne-id {
				type leafref {                
					path "/inv:inventory-cfg/inv:nes/inv:ne/inv:id";
				}
				description "Node id";
		    }
			leaf processId {
				type "uint32";
				description "";
			}
		}
	}
	rpc ospfv2comm-resetFrr {
		description "";
		input {
			leaf ne-id {
				type leafref {                
					path "/inv:inventory-cfg/inv:nes/inv:ne/inv:id";
				}
				description "Node id";
		    }
			leaf processId {
				type "uint32";
				description "";
			}
		}
	}
	*/
}
