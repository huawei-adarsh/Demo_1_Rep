/*
WARNING:
This yang model is just for fuction ONOS opensource project demo purpose only,
And is subject to change in future, Huawei does not commit provide compatibilty
in commercial product.
*/
submodule huawei-ac-ne-ospfv2-ospfv2comm-type {
	belongs-to "huawei-ac-ne-ospfv2"{
		prefix ospfv2;
	}
	organization "Huawei Technologies Co., Ltd";
	contact 
	"Huawei Industrial Base
	 Bantian, Longgang
	 Shenzhen 518129
	 People's Republic of China
   	 Website: http://www.huawei.com
	 Email: support@huawei.com
	";
	description "Support Restconf token add delete rpc";
	revision "2016-01-01" {
	    description "Initial revision.";
	}
	typedef ospfv2commImptRtProtocol {
		type enumeration {
			enum "default" {
				value 0;
				description "default";
			}
			enum "direct" {
				value 1;
				description "";
			}
			enum "ospf" {
				value 2;
				description "";
			}
			enum "isis" {
				value 3;
				description "";
			}
			enum "static" {
				value 4;
				description "";
			}
			enum "rip" {
				value 5;
				description "";
			}
			enum "bgp" {
				value 6;
				description "";
			}
		}
		description "";
	}
	typedef ospfv2commImporttRtProtocol {
		type enumeration {
			enum "direct" {
				value 0;
				description "";
			}
			enum "ospf" {
				value 1;
				description "";
			}
			enum "isis" {
				value 2;
				description "";
			}
			enum "static" {
				value 3;
				description "";
			}
			enum "rip" {
				value 4;
				description "";
			}
			enum "bgp" {
				value 5;
				description "";
			}
			enum "unr" {
				value 6;
				description "";
			}
		}
		description "";
	}
	typedef ospfv2commFilterRtProtocol {
		type enumeration {
			enum "default" {
				value 0;
				description "";
			}
			enum "direct" {
				value 1;
				description "";
			}
			enum "ospf" {
				value 2;
				description "";
			}
			enum "isis" {
				value 3;
				description "";
			}
			enum "static" {
				value 4;
				description "";
			}
			enum "rip" {
				value 5;
				description "";
			}
			enum "bgp" {
				value 6;
				description "";
			}
			enum "unr" {
				value 7;
				description "";
			}
		}
		description "";
	}
	typedef ospfv2commDomainIdType {
		type enumeration {
			enum "0005" {
				value 0;
				description "0005:";
			}
			enum "0105" {
				value 1;
				description "0105:";
			}
			enum "0205" {
				value 2;
				description "0205:";
			}
			enum "8005" {
				value 3;
				description "8005:";
			}
		}
		description "";
	}
	typedef ospfv2commPrePriority {
		type enumeration {
			enum "Critical" {
				value 0;
				description "Critical:";
			}
			enum "High" {
				value 1;
				description "High:";
			}
			enum "Medium" {
				value 2;
				description "Medium:";
			}
			enum "Low" {
				value 3;
				description "Low:";
			}
		}
		description "";
	}
	typedef ospfv2commPrefixPriority {
		type enumeration {
			enum "critical" {
				value 0;
				description "critical:";
			}
			enum "high" {
				value 1;
				description "high:";
			}
			enum "medium" {
				value 2;
				description "medium:";
			}
		}
		description "";
	}
	typedef ospfv2commDefaultCfgType {
		type enumeration {
			enum "cost" {
				value 0;
				description "cost:";
			}
			enum "tag" {
				value 1;
				description "tag:";
			}
			enum "type" {
				value 2;
				description "type:";
			}
		}
		description "";
	}
	typedef ospfv2commFilterType {
		type enumeration {
			enum "import" {
				value 0;
				description "import:";
			}
			enum "export" {
				value 1;
				description "export:";
			}
		}
		description "";
	}
	typedef ospfv2commFilter {
		type enumeration {
			enum "acl_name_or_num" {
				value 0;
				description "acl-name:";
			}
			enum "ip_prefix" {
				value 1;
				description "ip-prefix:";
			}
			enum "route_policy" {
				value 2;
				description "route-policy:";
			}
			enum "None" {
				value 3;
				description "No filter type is applied:";
			}
			enum "acl_num" {
				value 4;
				description "acl_num:";
			}
			enum "route_filter" {
				value 5;
				description "route-filter:";
			}
		}
		description "";
	}
	typedef ospfv2commFilterPolicy {
		type enumeration {
			enum "acl_name_or_num" {
				value 0;
				description "acl-name:";
			}
			enum "ip_prefix" {
				value 1;
				description "ip-prefix:";
			}
			enum "route_policy" {
				value 2;
				description "route-policy:";
			}
			enum "route_filter" {
				value 3;
				description "route-filter:";
			}
		}
		description "";
	}
	typedef ospfv2commRoutePolicy {
		type enumeration {
			enum "route_policy" {
				value 0;
				description "route-policy:";
			}
			enum "route_filter" {
				value 1;
				description "route-filter:";
			}
			enum "None" {
				value 2;
				description "No filter type is applied:";
			}
		}
		description "";
	}
	typedef ospfv2commFilterLsaOutPolicy {
		type enumeration {
			enum "none" {
				value 0;
				description "none:";
			}
			enum "acl_name_or_num" {
				value 1;
				description "acl-name or number:";
			}
		}
		description "";
	}
	typedef ospfv2commAreaFilterPolicy {
		type enumeration {
			enum "acl_name_or_num" {
				value 0;
				description "acl-name:";
			}
			enum "ip_prefix" {
				value 1;
				description "ip-prefix:";
			}
			enum "route_policy" {
				value 2;
				description "ip-prefix:";
			}
			enum "acl_num" {
				value 3;
				description "ip-prefix:";
			}
			enum "route_filter" {
				value 4;
				description "route-filter:";
			}
		}
		description "";
	}
	typedef ospfv2commAreaType {
		type enumeration {
			enum "Normal" {
				value 0;
				description "Normal:";
			}
			enum "Stub" {
				value 1;
				description "Stub:";
			}
			enum "Nssa" {
				value 2;
				description "Nssa:";
			}
		}
		description "";
	}
	typedef ospfv2commStubRouterFlag {
		type enumeration {
			enum "NoConfig" {
				value 0;
				description "NoConfig:";
			}
			enum "StubOnHand" {
				value 1;
				description "StubOnHand:";
			}
			enum "StubOnBoot" {
				value 2;
				description "StubOnBoot:";
			}
		}
		description "";
	}
	typedef ospfv2commOspfRouteType {
		type enumeration {
			enum "default" {
				value 0;
				description "default:";
			}
			enum "inter" {
				value 1;
				description "inter:";
			}
			enum "intra" {
				value 2;
				description "intra:";
			}
			enum "ase" {
				value 3;
				description "ase:";
			}
		}
		description "";
	}
	typedef ospfv2commDefRtConfigFlag {
		type enumeration {
			enum "DefRtAdv" {
				value 0;
				description "DefRtAdv:";
			}
			enum "Always" {
				value 1;
				description "Always:";
			}
			enum "Summary" {
				value 2;
				description "Summary:";
			}
		}
		description "";
	}
	typedef ospfv2commLsaType {
		type enumeration {
			enum "Router" {
				value 0;
				description "Router:";
			}
			enum "Network" {
				value 1;
				description "Network:";
			}
			enum "Sum_Net" {
				value 2;
				description "Sum-Net:";
			}
			enum "Sum_Asbr" {
				value 3;
				description "Sum-Asbr:";
			}
			enum "External" {
				value 4;
				description "External:";
			}
			enum "NSSA" {
				value 5;
				description "NSSA:";
			}
			enum "Opq_Link" {
				value 6;
				description "Opq-Link:";
			}
			enum "Opq_Area" {
				value 7;
				description "Opq-Area:";
			}
			enum "Opq_As" {
				value 8;
				description "Opq-As:";
			}
		}
		description "";
	}
	typedef ospfv2commOspfDebugType {
		type enumeration {
			enum "default" {
				value 0;
				description "default:";
			}
			enum "OspfDebug" {
				value 1;
				description "OspfDebug:";
			}
			enum "OspfTrace" {
				value 2;
				description "OspfTrace:";
			}
			enum "OspfPer" {
				value 3;
				description "OspfPer:";
			}
			enum "OspfMsgTrace" {
				value 4;
				description "OspfMsgTrace:";
			}
			enum "OspfTimer" {
				value 5;
				description "OspfTimer:";
			}
			enum "OspfJob" {
				value 6;
				description "OspfJob:";
			}
			enum "OspfMemVal" {
				value 7;
				description "OspfMemVal:";
			}
		}
		description "";
	}
	typedef ospfv2commOspfTnlType {
		type enumeration {
			enum "MPLSTE_TNLIF_TYPE_NONTE" {
				value 0;
				description "MPLSTE_TNLIF_TYPE_NONTE:";
			}
			enum "MPLSTE_TNLIF_TYPE_TE" {
				value 1;
				description "MPLSTE_TNLIF_TYPE_TE:";
			}
			enum "MPLSTE_TNLIF_TYPE_SHORTCUT" {
				value 2;
				description "MPLSTE_TNLIF_TYPE_SHORTCUT:";
			}
			enum "MPLSTE_TNLIF_TYPE_FA" {
				value 3;
				description "MPLSTE_TNLIF_TYPE_FA:";
			}
		}
		description "";
	}
	typedef ospfv2commOspfMetricType {
		type enumeration {
			enum "MPLSTE_TNLIF_METRIC_RELATIVE" {
				value 0;
				description "MPLSTE_TNLIF_METRIC_RELATIVE:";
			}
			enum "MPLSTE_TNLIF_METRIC_ABSOLUTE" {
				value 1;
				description "MPLSTE_TNLIF_METRIC_ABSOLUTE:";
			}
		}
		description "";
	}
	typedef ospfv2commIfTnlType {
		type enumeration {
			enum "IGP_shortcut" {
				value 0;
				description "IGP_shortcut:";
			}
			enum "Forwarding_Adjacency" {
				value 1;
				description "Forwarding_Adjacency:";
			}
		}
		description "";
	}
	typedef ospfv2commTunnelIGPType {
		type enumeration {
			enum "MPLSTE_TNLIF_IGP_NONE" {
				value 0;
				description "MPLSTE_TNLIF_IGP_NONE:";
			}
			enum "MPLSTE_TNLIF_IGP_ISIS" {
				value 1;
				description "MPLSTE_TNLIF_IGP_ISIS:";
			}
			enum "MPLSTE_TNLIF_IGP_OSPF" {
				value 2;
				description "MPLSTE_TNLIF_IGP_OSPF:";
			}
			enum "MPLSTE_TNLIF_IGP_BOTH" {
				value 3;
				description "MPLSTE_TNLIF_IGP_BOTH:";
			}
		}
		description "";
	}
	typedef ospfv2commNetworkType {
		type enumeration {
			enum "broadcast" {
				value 0;
				description "broadcast:";
			}
			enum "nbma" {
				value 1;
				description "nbma:";
			}
			enum "p2mp" {
				value 2;
				description "p2mp:";
			}
			enum "p2p" {
				value 3;
				description "p2p:";
			}
		}
		description "";
	}
	typedef ospfv2commIntfAuthenMode {
		type enumeration {
			enum "none" {
				value 0;
				description "none:";
			}
			enum "null" {
				value 1;
				description "null:";
			}
			enum "hmac-sha256" {
				value 2;
				description "null:";
			}
			enum "md5" {
				value 3;
				description "md5:";
			}
			enum "hmac-md5" {
				value 4;
				description "hmac-md5:";
			}
			enum "simple" {
				value 5;
				description "simple:";
			}
			enum "keychain" {
				value 6;
				description "keychain:";
			}
		}
		description "";
	}
	typedef ospfv2commAreaAuthenMode {
		type enumeration {
			enum "none" {
				value 0;
				description "none:";
			}
			enum "md5" {
				value 1;
				description "md5:";
			}
			enum "hmac-sha256" {
				value 2;
				description "hmac-sha256";
			}
			enum "hmac-md5" {
				value 3;
				description "hmac-md5:";
			}
			enum "simple" {
				value 4;
				description "simple:";
			}
			enum "keychain" {
				value 5;
				description "keychain:";
			}
		}
		description "";
	}
	typedef ospfv2commAuthenTextType {
		type enumeration {
			enum "none" {
				value 0;
				description "none:";
			}
			enum "plain" {
				value 1;
				description "plain:";
			}
			enum "cipher" {
				value 2;
				description "cipher:";
			}
		}
		description "";
	}
	typedef ospfv2commIntfState {
		type enumeration {
			enum "Down" {
				value 0;
				description "Down:";
			}
			enum "Waiting" {
				value 1;
				description "Waiting:";
			}
			enum "P-2-P" {
				value 2;
				description "P-2-P:";
			}
			enum "DR" {
				value 3;
				description "DR:";
			}
			enum "BDR" {
				value 4;
				description "BDR:";
			}
			enum "DROTHER" {
				value 5;
				description "DROTHER:";
			}
			enum "Loopback" {
				value 6;
				description "Loopback:";
			}
		}
		description "";
	}
	typedef ospfv2commIntfType {
		type enumeration {
			enum "Broadcast" {
				value 0;
				description "Broadcast:";
			}
			enum "NBMA" {
				value 1;
				description "NBMA:";
			}
			enum "P2P" {
				value 2;
				description "P2P:";
			}
			enum "Virtual" {
				value 3;
				description "Virtual:";
			}
			enum "P2MP" {
				value 4;
				description "P2MP:";
			}
		}
		description "";
	}
	typedef ospfv2commGRLastExitReason {
		type enumeration {
			enum "none" {
				value 0;
				description "none:";
			}
			enum "success" {
				value 1;
				description "success exit";
			}
			enum "grace period expire" {
				value 2;
				description "grace period expired";
			}
			enum "recv flush grace lsa" {
				value 3;
				description "received flushed grace LSA";
			}
			enum "recv change lsa" {
				value 4;
				description "flooding change LSA";
			}
			enum "recv two grace lsa" {
				value 5;
				description "received multiple grace LSA";
			}
			enum "recv one way hello" {
				value 6;
				description "received 1-way hello packet";
			}
			enum "policy check fail" {
				value 7;
				description "policy check failed for received grace LSA";
			}
			enum "nbr reset" {
				value 8;
				description "neighbor reset";
			}
			enum "if change" {
				value 9;
				description "interface state change";
			}
			enum "proc change" {
				value 10;
				description "graceful restart unconfigured at pro"
+ "cess level";
			}
		}
		description "";
	}
	typedef ospfv2commGRState {
		type enumeration {
			enum "Normal" {
				value 0;
				description "Normal:";
			}
			enum "Helper" {
				value 1;
				description "Helper:";
			}
			enum "NA" {
				value 2;
				description "NA:";
			}
		}
		description "";
	}
	typedef ospfv2commLdpState {
		type enumeration {
			enum "Down" {
				value 0;
				description "Down:";
			}
			enum "Up" {
				value 1;
				description "Up:";
			}
			enum "GR" {
				value 2;
				description "GR:";
			}
			/*
			enum "---" {
				value 3;
				description "---";
			} */
		}
		description "";
	}
	typedef ospfv2commBFDState {
		type enumeration {
			enum "Unknown" {
				value 0;
				description "Unknown:";
			}
			enum "Down" {
				value 1;
				description "Down:";
			}
			enum "Up" {
				value 2;
				description "Up:";
			}
		}
		description "";
	}
	typedef ospfv2commIntfTeState {
		type enumeration {
			enum "MPLS TE not enabled" {
				value 0;
				description "MPLS TE not enabled:";
			}
			enum "MPLS TE enabled" {
				value 1;
				description "MPLS TE enabled:";
			}
		}
		description "";
	}
	typedef ospfv2commNbrState {
		type enumeration {
			enum "Down" {
				value 0;
				description "Down:";
			}
			enum "Init" {
				value 1;
				description "Init:";
			}
			enum "Attempt" {
				value 2;
				description "Attempt:";
			}
			enum "2-Way" {
				value 3;
				description "2-Way:";
			}
			enum "ExStart" {
				value 4;
				description "ExStart:";
			}
			enum "Exchange" {
				value 5;
				description "Exchange:";
			}
			enum "Loading" {
				value 6;
				description "Loading:";
			}
			enum "Full" {
				value 7;
				description "Full:";
			}
		}
		description "";
	}
	typedef ospfv2commNbrDownImmReason {
		type enumeration {
			enum "Neighbor Down Due to Inactivity" {
				value 0;
				description "Neighbor Down Due to Inactivity:";
			}
			enum "Neighbor Down Due to LL Down" {
				value 1;
				description "Neighbor Down Due to LL Down:";
			}
			enum "Neighbor Down Due to Kill Neighbor" {
				value 2;
				description "Neighbor Down Due to Kill Neighbor:";
			}
			enum "Neighbor Down Due to 1-Wayhello Received" {
				value 3;
				description "Neighbor Down Due to 1-Wayhello Received:";
			}
			enum "Neighbor-Down-Due-to-AdjOK" {
				value 4;
				description "Neighbor Down Due to AdjOK?:";
			}
			enum "Neighbor Down Due to SequenceNum Mismatch" {
				value 5;
				description "Neighbor Down Due to SequenceNum Mismatch:";
			}
			enum "Neighbor Down Due to BadLSreq" {
				value 6;
				description "Neighbor Down Due to BadLSreq:";
			}
		}
		description "";
	}
	typedef ospfv2commNbrDownPrimReason {
		type enumeration {
			enum "Down reason Init Value" {
				value 0;
				description "Down reason Init Value:";
			}
			enum "Hello Not Seen" {
				value 1;
				description "Hello Not Seen:";
			}
			enum "Interface Parameter Mismatch" {
				value 2;
				description "Interface Parameter Mismatch:";
			}
			enum "Logical Interface State Change" {
				value 3;
				description "Logical Interface State Change:";
			}
			enum "Link Fault or Interface Configuration Change" {
				value 4;
				description "Link Fault or Interface Configuration Change:";
			}
			enum "OSPF Process Reset" {
				value 5;
				description "OSPF Process Reset:";
			}
			enum "Area reset" {
				value 6;
				description "Area reset:";
			}
			enum "Area Option Mis-match" {
				value 7;
				description "Area Option Mis-match:";
			}
			enum "Vlink Peer Not Reachable" {
				value 8;
				description "Vlink Peer Not Reachable:";
			}
			enum "Sham-Link Unreachable" {
				value 9;
				description "Sham-Link Unreachable:";
			}
			enum "Undo Network Command" {
				value 10;
				description "Undo Network Command:";
			}
			enum "Undo NBMA Peer" {
				value 11;
				description "Undo NBMA Peer:";
			}
			enum "Passive Interface Down" {
				value 12;
				description "Passive Interface Down:";
			}
			enum "Opaque Capability Enabled" {
				value 13;
				description "Opaque Capability Enabled:";
			}
			enum "Opaque Capability Disabled" {
				value 14;
				description "Opaque Capability Disabled:";
			}
			enum "Virtual Interface State Change" {
				value 15;
				description "Virtual Interface State Change:";
			}
			enum "BFD Session Down" {
				value 16;
				description "BFD Session Down:";
			}
			enum "Retransmission Limit Exceed" {
				value 17;
				description "Retransmission Limit Exceed:";
			}
			enum "1-Wayhello Received" {
				value 18;
				description "1-Wayhello Received:";
			}
			enum "Router State Change from DR or BDR to DROTHER" {
				value 19;
				description "Router State Change from DR or BDR t"
+ "o DROTHER:";
			}
			enum "Neighbor State Change from DR or BDR to DROTHER" {
				value 20;
				description "Neighbor State Change from DR or BDR"
+ " to DROTHER:";
			}
			enum "NSSA Area Configure Change" {
				value 21;
				description "NSSA Area Configure Change:";
			}
			enum "Stub Area Configure Change" {
				value 22;
				description "Stub Area Configure Change:";
			}
			enum "Received Invalid DD Packet" {
				value 23;
				description "Received Invalid DD Packet:";
			}
			enum "Not Received DD during RouterDeadInterval" {
				value 24;
				description "Not Received DD during RouterDeadInterval:";
			}
			enum "M-I-MS-bit-or-SequenceNum-Incorrect" {
				value 25;
				description "M,I,MS bit or SequenceNum Incorrect:";
			}
			enum "Unable-Opaque-Capability-Find-9-10-11-Type-Lsa" {
				value 26;
				description "Unable Opaque Capability,Find 9,10,1"
+ "1 Type Lsa:";
			}
			enum "Not-NSSA-Find-7-Type-Lsa-in-Summary-List" {
				value 27;
				description "Not NSSA,Find 7 Type Lsa in Summary List:";
			}
			enum "LSrequest-Packet-Unknown-Reason" {
				value 28;
				description "LSrequest Packet,Unknown Reason:";
			}
			enum "NSSA-or-STUB-Area-Find-5-11-Type-Lsa" {
				value 29;
				description "NSSA or STUB Area,Find 5 ,11 Type Lsa:";
			}
			enum "LSrequest-Packet-Request-Lsa-is-Not-in-the-Lsdb" {
				value 30;
				description "LSrequest Packet,Request Lsa is Not "
+ "in the Lsdb:";
			}
			enum "LSrequest-Packet-exist-same-lsa-in-the-Lsdb" {
				value 31;
				description "LSrequest Packet, exist same lsa in the Lsdb:";
			}
			enum "LSrequest-Packet-exist-newer-lsa-in-the-Lsdb" {
				value 32;
				description "LSrequest Packet, exist newer lsa in"
+ " the Lsdb:";
			}
			enum "Neighbor state was not full when LSDB overflow" {
				value 33;
				description "Neighbor state was not full when LSD"
+ "B overflow:";
			}
			enum "Filter LSA configuration change" {
				value 34;
				description "Filter LSA configuration change:";
			}
			enum "ACL changed for Filter LSA" {
				value 35;
				description "ACL changed for Filter LSA:";
			}
			enum "Reset Ospf Peer" {
				value 36;
				description "Reset Ospf Peer:";
			}
			enum "Interface Reset" {
				value 37;
				description "Interface Reset:";
			}
			enum "Undo-OSPF-Interface-Undo-area-Undo-network" {
				value 38;
				description "Undo OSPF Interface, Undo area, Undo network:";
			}
			enum "UNDO OSPF Area" {
				value 39;
				description "UNDO OSPF Area:";
			}
			enum "CPU Overload" {
				value 40;
				description "CPU Overload:";
			}
			enum "Interface State Changed to Standby" {
				value 41;
				description "Interface State Changed to Standby:";
			}
			enum "Undo Router-Id" {
				value 42;
				description "Undo Router-Id:";
			}
			enum "Neighbor Router-Id changed or Ip Conflicted" {
				value 43;
				description "Neighbor Router-Id changed or Ip Conflicted:";
			}
			enum "Component is in Implement stat" {
				value 44;
				description "Component is in Implement stat:";
			}
			enum "Seqeunce Number mismatched" {
				value 45;
				description "Seqeunce Number mismatched:";
			}
			enum "I Bit Incorrect in DD" {
				value 46;
				description "I Bit Incorrect in DD:";
			}
			enum "MS Bit Incorrect in DD" {
				value 47;
				description "MS Bit Incorrect in DD:";
			}
			enum "Options Incorrect in DD" {
				value 48;
				description "Options Incorrect in DD:";
			}
			enum "Received MTU mismatched DD Packet" {
				value 49;
				description "Received MTU mismatched DD Packet:";
			}
			enum "OSPF Process Shutdown" {
				value 50;
				description "OSPF Process Shutdown:";
			}
			enum "DD retrans times upto limit" {
				value 51;
				description "DD retrans times upto limit:";
			}
			enum "Undo-OSPF-Interface-Undo-area" {
				value 52;
				description "Undo OSPF Interface, Undo area:";
			}
		}
		description "";
	}
	typedef ospfv2commNbrMode {
		type enumeration {
			enum "Slave" {
				value 0;
				description "Slave:";
			}
			enum "Master" {
				value 1;
				description "Master:";
			}
		}
		description "";
	}
	typedef ospfv2commLSDBOptions {
		type enumeration {
			enum "ABR" {
				value 0;
				description "ABR:";
			}
			enum "ASBR" {
				value 1;
				description "ASBR:";
			}
			enum "ASBR ABR" {
				value 2;
				description "ASBR ABR:";
			}
			enum "ABR  VIRTUAL" {
				value 3;
				description "ABR VIRTUAL:";
			}
			enum "ASBR  ABR  VIRTUAL" {
				value 4;
				description "ASBR ABR VIRTUAL :";
			}
		}
		description "";
	}
	typedef ospfv2commLSDBOption {
		type enumeration {
			enum "None" {
				value 0;
				description "None:";
			}
			enum "E" {
				value 1;
				description "E:";
			}
			enum "MC" {
				value 2;
				description "MC:";
			}
			enum "MC E" {
				value 3;
				description "MC E:";
			}
			enum "N-P" {
				value 4;
				description "N/P:";
			}
			enum "N-P-E" {
				value 5;
				description "N/P E:";
			}
			enum "N-P-MC" {
				value 6;
				description "N/P MC:";
			}
			enum "N-P-MC-E" {
				value 7;
				description "N/P MC E:";
			}
			enum "EA" {
				value 8;
				description "EA:";
			}
			enum "EA E" {
				value 9;
				description "EA E:";
			}
			enum "EA MC" {
				value 10;
				description "EA MC:";
			}
			enum "EA MC E" {
				value 11;
				description "EA MC E:";
			}
			enum "EA-N-P" {
				value 12;
				description "EA N/P:";
			}
			enum "EA-N-P-E" {
				value 13;
				description "EA N/P E:";
			}
			enum "EA-N-P-MC" {
				value 14;
				description "EA N/P MC:";
			}
			enum "EA-N-P-MC-E" {
				value 15;
				description "EA N/P MC E:";
			}
			enum "DC" {
				value 16;
				description "DC:";
			}
			enum "DC E" {
				value 17;
				description "DC E:";
			}
			enum "DC MC" {
				value 18;
				description "DC MC:";
			}
			enum "DC MC E" {
				value 19;
				description "DC MC E:";
			}
			enum "DC-N-P" {
				value 20;
				description "DC N/P:";
			}
			enum "DC-N-P-E" {
				value 21;
				description "DC N/P E:";
			}
			enum "DC-N-P-MC" {
				value 22;
				description "DC N/P MC:";
			}
			enum "DC-N-P-MC-E" {
				value 23;
				description "DC N/P MC E:";
			}
			enum "DC EA" {
				value 24;
				description "DC EA:";
			}
			enum "DC EA E" {
				value 25;
				description "DC EA E:";
			}
			enum "DC EA MC" {
				value 26;
				description "DC EA MC:";
			}
			enum "DC EA MC E" {
				value 27;
				description "DC EA MC E:";
			}
			enum "DC-EA-N-P" {
				value 28;
				description "DC EA N/P:";
			}
			enum "DC-EA-N-P-E" {
				value 29;
				description "DC EA N/P E:";
			}
			enum "DC-EA-N-P-MC" {
				value 30;
				description "DC EA N/P MC:";
			}
			enum "DC-EA-N-P-MC-E" {
				value 31;
				description "DC EA N/P MC E:";
			}
			enum "DN" {
				value 32;
				description "DN:";
			}
			enum "E DN" {
				value 33;
				description "E DN:";
			}
			enum "N-P-DN" {
				value 34;
				description "N/P DN:";
			}
		}
		description "";
	}
	typedef ospfv2commLSDBLinkType {
		type enumeration {
			enum "none" {
				value 0;
				description "none:";
			}
			enum "P-2-P" {
				value 1;
				description "P-2-P:";
			}
			enum "TransNet" {
				value 2;
				description "TransNet:";
			}
			enum "StubNet" {
				value 3;
				description "StubNet:";
			}
			enum "Virtual" {
				value 4;
				description "Virtual:";
			}
		}
		description "";
	}
	typedef ospfv2commPathType {
		type enumeration {
			enum "Unkown" {
				value 0;
				description "Unkown:";
			}
			enum "Intra-area" {
				value 1;
				description "Intra-area:";
			}
			enum "Transit" {
				value 2;
				description "Transit:";
			}
			enum "Stub" {
				value 3;
				description "Stub:";
			}
			enum "Inter-area" {
				value 4;
				description "Inter-area:";
			}
			enum "Direct" {
				value 5;
				description "Direct:";
			}
			enum "Type1" {
				value 6;
				description "Type1:";
			}
			enum "Type2" {
				value 7;
				description "Type2:";
			}
		}
		description "";
	}
	typedef ospfv2commRouterType {
		type enumeration {
			enum "Normal" {
				value 0;
				description "Normal:";
			}
			enum "ASBR" {
				value 1;
				description "ASBR:";
			}
			enum "ABR" {
				value 2;
				description "ABR:";
			}
			enum "ABR-ASBR" {
				value 3;
				description "ABR/ASBR:";
			}
		}
		description "";
	}
	typedef ospfv2commExternalRouteType {
		type enumeration {
			enum "Type1" {
				value 0;
				description "Type1:";
			}
			enum "Type2" {
				value 1;
				description "Type2:";
			}
		}
		description "";
	}
	typedef ospfv2commRouteSourceType {
		type enumeration {
			enum "Local" {
				value 0;
				description "Local:";
			}
			enum "unknow" {
				value 1;
				description "unknow:";
			}
		}
		description "";
	}
	typedef ospfv2commOSPFSyncState {
		type enumeration {
			enum "Sync-Achieved" {
				value 0;
				description "Sync-Achieved:";
			}
			enum "HoldMaxCost" {
				value 1;
				description "HoldMaxCost:";
			}
			enum "Init" {
				value 2;
				description "Init:";
			}
		}
		description "";
	}
	typedef ospfv2commSpfIntevalFlag {
		type enumeration {
			enum "intelligent-timer" {
				value 0;
				description "intelligent-timer:";
			}
			enum "timer" {
				value 1;
				description "timer:";
			}
			enum "millisecond" {
				value 2;
				description "millisecond:";
			}
		}
		description "";
	}
	typedef ospfv2commLSDBOptionFlag {
		type enumeration {
			enum "Null" {
				value 0;
				description "0:";
			}
			enum "ABR" {
				value 1;
				description "ABR:";
			}
			enum "ASBR" {
				value 2;
				description "ASBR:";
			}
			enum "ASBR ABR" {
				value 3;
				description "ASBR ABR:";
			}
			enum "VIRTUAL" {
				value 4;
				description "VIRTUAL:";
			}
			enum "ABR VIRTUAL" {
				value 5;
				description "ABR VIRTUAL:";
			}
			enum "ASBR VIRTUAL" {
				value 6;
				description "ASBR VIRTUAL:";
			}
			enum "ASBR ABR VIRTUAL" {
				value 7;
				description "ASBR ABR VIRTUAL:";
			}
			enum "Nt" {
				value 8;
				description "Nt:";
			}
			enum "ABR Nt" {
				value 9;
				description "ABR Nt:";
			}
			enum "ASBR Nt" {
				value 10;
				description "ASBR Nt:";
			}
			enum "ASBR ABR Nt" {
				value 11;
				description "ASBR ABR Nt:";
			}
			enum "VIRTUAL Nt" {
				value 12;
				description "VIRTUAL Nt:";
			}
			enum "ABR VIRTUAL Nt" {
				value 13;
				description "ABR VIRTUAL Nt:";
			}
			enum "ASBR VIRTUAL Nt" {
				value 14;
				description "ASBR VIRTUAL Nt:";
			}
			enum "ASBR ABR VIRTUAL Nt" {
				value 15;
				description "ASBR ABR VIRTUAL Nt:";
			}
		}
		description "";
	}
	typedef ospfv2commTopology {
		type enumeration {
			enum "base" {
				value 0;
				description "base:";
			}
		}
		description "";
	}
	typedef ospfv2commGRFilterType {
		type enumeration {
			enum "acl_name" {
				value 0;
				description "acl-name:";
			}
			enum "ip_prefix" {
				value 1;
				description "ip-prefix:";
			}
			enum "acl_num" {
				value 2;
				description "acl-name:";
			}
			enum "none" {
				value 3;
				description "none:";
			}
		}
		description "";
	}
	typedef ospfv2sockRegStatus {
		type enumeration {
			enum "ICUSCK_COMP_INIT" {
				value 0;
				description "ICUSCK_COMP_INIT";
			}
			enum "ICUSCK_COMP_REGISTER" {
				value 1;
				description "ICUSCK_COMP_REGISTER";
			}
			enum "ICUSCK_COMP_UNREGISTER" {
				value 2;
				description "ICUSCK_COMP_UNREGISTER";
			}
			enum "ICUSCK_COMP_PREPAIR_DOPRIMARY" {
				value 3;
				description "ICUSCK_COMP_PREPAIR_DOPRIMARY:";
			}
			enum "ICUSCK_COMP_WAIT_APP_DOPRIMARY" {
				value 4;
				description "ICUSCK_COMP_WAIT_APP_DOPRIMARY:";
			}
			enum "ICUSCK_COMP_WAIT_SCK_SWITCH_END" {
				value 5;
				description "ICUSCK_COMP_WAIT_SCK_SWITCH_END:";
			}
			enum "ICUSCK_COMP_WAIT_APP_SWITCH_END" {
				value 6;
				description "ICUSCK_COMP_WAIT_APP_SWITCH_END:";
			}
			enum "ICUSCK_COMP_RUN_ALONE" {
				value 7;
				description "ICUSCK_COMP_RUN_ALONE:";
			}
			enum "ICUSCK_COMP_WAIT_BBTYPE_ACK" {
				value 8;
				description "ICUSCK_COMP_WAIT_BBTYPE_ACK:";
			}
			enum "ICUSCK_COMP_WAIT_APP_BBOVER" {
				value 9;
				description "ICUSCK_COMP_WAIT_APP_BBOVER:";
			}
			enum "ICUSCK_COMP_WAIT_SCK_BBOVER" {
				value 10;
				description "ICUSCK_COMP_WAIT_SCK_BBOVER:";
			}
			enum "ICUSCK_COMP_WAIT_APP_BBOVER_ACK" {
				value 11;
				description "ICUSCK_COMP_WAIT_APP_BBOVER_ACK:";
			}
			enum "ICUSCK_COMP_RUN_TOGETHER" {
				value 12;
				description "ICUSCK_COMP_RUN_TOGETHER:";
			}
			enum "ICUSCK_COMP_STATE_MAX" {
				value 13;
				description "ICUSCK_COMP_STATE_MAX:";
			}
		}
		description "";
	}
	typedef ospfv2sockFSMStatus {
		type enumeration {
			enum "ICUSCK_ENTRY_STATE_INIT" {
				value 0;
				description "ICUSCK_ENTRY_STATE_INIT";
			}
			enum "ICUSCK_ENTRY_STATE_REQUESTING" {
				value 1;
				description "ICUSCK_ENTRY_STATE_REQUESTING";
			}
			enum "ICUSCK_ENTRY_STATE_CREATING" {
				value 2;
				description "ICUSCK_ENTRY_STATE_CREATING";
			}
			enum "ICUSCK_ENTRY_STATE_RUN" {
				value 3;
				description "ICUSCK_ENTRY_STATE_RUN:";
			}
			enum "ICUSCK_ENTRY_STATE_SMOOTHING" {
				value 4;
				description "ICUSCK_ENTRY_STATE_SMOOTHING:";
			}
			enum "ICUSCK_ENTRY_STATE_WAIT_CLOSING" {
				value 5;
				description "ICUSCK_ENTRY_STATE_WAIT_CLOSING:";
			}
			enum "ICUSCK_ENTRY_STATE_CLOSING" {
				value 6;
				description "ICUSCK_ENTRY_STATE_CLOSING:";
			}
			enum "ICUSCK_ENTRY_STATE_ATTACHING" {
				value 7;
				description "ICUSCK_ENTRY_STATE_ATTACHING:";
			}
			enum "ICUSCK_ENTRY_STATE_DETACHING" {
				value 8;
				description "ICUSCK_ENTRY_STATE_DETACHING:";
			}
			enum "ICUSCK_ENTRY_STATE_MAX" {
				value 9;
				description "ICUSCK_ENTRY_STATE_MAX:";
			}
		}
		description "";
	}
	typedef ospfv2RecvPipeStatus {
		type enumeration {
			enum "CLOSE" {
				value 0;
				description "CLOSE";
			}
			enum "WAIT OPEN ACK" {
				value 1;
				description "WAIT OPEN ACK";
			}
			enum "OPEN" {
				value 2;
				description "OPEN";
			}
			enum "CONGESTION" {
				value 3;
				description "CONGESTION:";
			}
			enum "WAIT CLOSE ACK" {
				value 4;
				description "WAIT CLOSE ACK:";
			}
		}
		description "";
	}
	typedef ospfv2commPktStatType {
		type enumeration {
			enum "PKTSTATTYPE_EXTERNAL" {
				value 0;
				description "PKTSTATTYPE_EXTERNAL:";
			}
			enum "PKTSTATTYPE_INTERNAL" {
				value 1;
				description "PKTSTATTYPE_INTERNAL:";
			}
		}
		description "";
	}
	typedef ospfv2BfdStatus {
		type enumeration {
			enum "Unknown" {
				value 0;
				description "Unknown:";
			}
			enum "Down" {
				value 1;
				description "Down:";
			}
			enum "Up" {
				value 2;
				description "Up:";
			}
		}
		description "";
	}
	typedef ospfv2commBorderRouter {
		type enumeration {
			enum "NORMAL" {
				value 0;
				description "NORMAL";
			}
			enum "AREA" {
				value 1;
				description "AREA";
			}
			enum "AS" {
				value 2;
				description "AS";
			}
			enum "AREA AS" {
				value 3;
				description "AREA AS";
			}
			enum "NSSA" {
				value 4;
				description "NSSA";
			}
			enum "AREA NSSA" {
				value 5;
				description "AREA NSSA";
			}
			enum "AS NSSA" {
				value 6;
				description "AS NSSA";
			}
			enum "AREA AS NSSA" {
				value 7;
				description "AREA AS NSSA";
			}
		}
		description "";
	}
	typedef ospfv2commIETFMode {
		type enumeration {
			enum "Non-Standard IETF Mode" {
				value 0;
				description "Non-Standard IETF Mode";
			}
			enum "Standard IETF Mode" {
				value 1;
				description "Standard IETF Mode";
			}
		}
		description "";
	}
	typedef ospfv2commBackupType {
		type enumeration {
			enum "LFA LINK" {
				value 0;
				description "LFA LINK:";
			}
			enum "LFA LINK-NODE" {
				value 1;
				description "LFA LINK-NODE:";
			}
			enum "REMOTE LFA LINK" {
				value 2;
				description "REMOTE LFA LINK:";
			}
			enum "REMOTE LFA LINK-NODE" {
				value 3;
				description "REMOTE LFA LINK-NODE:";
			}
		}
		description "";
	}
	typedef ospfv2commTunnelType {
		type enumeration {
			enum "LDP" {
				value 0;
				description "LDP:";
			}
		}
		description "";
	}
	typedef ospfv2NSSATransState {
		type enumeration {
			enum "none" {
				value 0;
				description "";
			}
			enum "Enabled" {
				value 1;
				description "Enabled";
			}
			enum "Elected" {
				value 2;
				description "Elected";
			}
			enum "Disabled" {
				value 3;
				description "Disabled";
			}
		}
		description "";
	}
	typedef ospfv2NSSATransRole {
		type enumeration {
			enum "none" {
				value 0;
				description "";
			}
			enum "Always" {
				value 1;
				description "Always";
			}
			enum "Candidate" {
				value 2;
				description "Candidate";
			}
		}
		description "";
	}
	typedef ospfv2AsbrSumStatus {
		type enumeration {
			enum "DoNot Advertise" {
				value 0;
				description "DoNot Advertise";
			}
			enum "Advertise" {
				value 1;
				description "Advertise";
			}
		}
		description "";
	}
	typedef ospfv2commHstScope {
		type enumeration {
			enum "Link-Scope" {
				value 0;
				description "Link-Scope";
			}
			enum "Area-Scope" {
				value 1;
				description "Area-Scope";
			}
			enum "AS-Scope" {
				value 2;
				description "AS-Scope";
			}
		}
		description "";
	}
	typedef ospfv2RtrIdConState {
		type enumeration {
			enum "Normal" {
				value 0;
				description "Normal";
			}
			enum "Wait select" {
				value 1;
				description "Wait select";
			}
			enum "Selecting" {
				value 2;
				description "Selecting";
			}
			enum "RtrId Changed" {
				value 3;
				description "RtrId Changed";
			}
			enum "Suspend" {
				value 4;
				description "Suspend";
			}
			enum "NA" {
				value 5;
				description "Not applicable";
			}
		}
		description "";
	}
	typedef ospfv2commNbrDispGRState {
		type enumeration {
			enum "Normal" {
				value 0;
				description "Normal:";
			}
			enum "Doing GR" {
				value 1;
				description "Doing GR:";
			}
			enum "Helper" {
				value 2;
				description "Helper:";
			}
			enum "NA" {
				value 3;
				description "NA:";
			}
		}
		description "";
	}
	typedef ospfv2HelperCapabality {
		type enumeration {
			enum "disabled" {
				value 0;
				description "disabled";
			}
			enum "enabled" {
				value 1;
				description "enabled";
			}
		}
		description "";
	}
	typedef ospfv2HelperSupport {
		type enumeration {
			enum "none" {
				value 0;
				description "none";
			}
			enum "planned-strict-lsa-check" {
				value 1;
				description "planned, strict lsa check";
			}
			enum "un-planned-strict-lsa-check" {
				value 2;
				description "un-planned, strict lsa check";
			}
			enum "planned-un-planned-strict-lsa-check" {
				value 3;
				description "planned, un-planned, strict lsa check";
			}
			enum "ignore-external-lsa-check" {
				value 4;
				description "ignore external lsa check";
			}
			enum "planned-ignore-external-lsa-check" {
				value 5;
				description "planned, ignore external lsa check";
			}
			enum "un-planned-ignore-external-lsa-check" {
				value 6;
				description "un-planned, ignore external lsa check";
			}
			enum "planned-un-planned-ignore-external-lsa-check" {
				value 7;
				description "planned, un-planned, ignore external"
+ " lsa check";
			}
			enum "never" {
				value 8;
				description "never";
			}
			enum "planned-and-un-planned-strict-lsa-check" {
				value 12;
				description "planned and un-planned, strict lsa check";
			}
			enum "lsa checking ignore" {
				value 13;
				description "lsa checking ignore";
			}
			enum "planned" {
				value 14;
				description "planned";
			}
			enum "un-planned-lsa-checking-ignore" {
				value 15;
				description "un-planned, lsa checking ignore";
			}
			enum "planned and unplanned" {
				value 16;
				description "planned and unplanned";
			}
		}
		description "";
	}
	typedef ospfv2OnHelper {
		type enumeration {
			enum "none" {
				value 0;
				description "none";
			}
			enum "successful exit" {
				value 1;
				description "successful exit";
			}
			enum "grace period expired" {
				value 2;
				description "grace period expired";
			}
			enum "received flushed grace LSA" {
				value 3;
				description "received flushed grace LSA";
			}
			enum "flooding changed LSA" {
				value 4;
				description "flooding changed LSA";
			}
			enum "policy check failed for received grace LSA" {
				value 6;
				description "policy check failed for received grace LSA";
			}
			enum "neighbor reset" {
				value 7;
				description "neighbor reset";
			}
			enum "interface status changed" {
				value 8;
				description "interface status changed";
			}
			enum "graceful restart unconfigured at process level" {
				value 9;
				description "graceful restart unconfigured at pro"
+ "cess level";
			}
			enum "grace lsa not found" {
				value 10;
				description "grace lsa not found";
			}
		}
		description "";
	}
	typedef ospfv2GRNbrState {
		type enumeration {
			enum "Normal" {
				value 0;
				description "Normal";
			}
			enum "Restarter" {
				value 1;
				description "Restarter";
			}
		}
		description "";
	}
	typedef ospfv2SupprReach {
		type enumeration {
			enum "false" {
				value 0;
				description "false:";
			}
			enum "true" {
				value 1;
				description "true:";
			}
			enum "Disable" {
				value 2;
				description "Disable:";
			}
			enum "Enable" {
				value 3;
				description "Enable:";
			}
			enum "Not Configured" {
				value 4;
				description "Not Configured:";
			}
		}
		description "";
	}
	typedef ospfv2ProcAutoCfgState {
		type enumeration {
			enum "None" {
				value 0;
				description "None";
			}
			enum "Enable" {
				value 1;
				description "Enable";
			}
		}
		description "";
	}
	typedef ospfv2IfAutoCfgState {
		type enumeration {
			enum "None" {
				value 0;
				description "None";
			}
			enum "Disable" {
				value 1;
				description "Disable";
			}
		}
		description "";
	}
	typedef ospfv2FldCtrlTechnique {
		type enumeration {
			enum "None" {
				value 0;
				description "Flood control without any type";
			}
			enum "number" {
				value 1;
				description "Specify the update packet number to send";
			}
			enum "timer-interval" {
				value 2;
				description "Specify the update packet timer inte"
+ "rval to send";
			}
		}
		description "";
	}
	typedef ospfv2GRSupport {
		type enumeration {
			enum "none" {
				value 0;
				description "none";
			}
			enum "planned-totally" {
				value 1;
				description "planned, totally";
			}
			enum "un-planned-totally" {
				value 2;
				description "un-planned, totally";
			}
		}
		description "";
	}
	typedef ospfv2GRReason {
		type enumeration {
			enum "Unknown" {
				value 0;
				description "Unknown";
			}
			enum "Software" {
				value 1;
				description "Software";
			}
			enum "Upgrade" {
				value 2;
				description "Upgrade";
			}
		}
		description "";
	}
	typedef ospfv2OnGRExitReason {
		type enumeration {
			enum "none" {
				value 0;
				description "none";
			}
			enum "successful exit" {
				value 1;
				description "successful exit";
			}
			enum "grace period expired" {
				value 2;
				description "grace period expired";
			}
			enum "received flushed grace LSA" {
				value 3;
				description "received flushed grace LSA";
			}
			enum "flooding changed LSA" {
				value 4;
				description "flooding changed LSA";
			}
			enum "policy check failed for received grace LSA" {
				value 6;
				description "policy check failed for received grace LSA";
			}
			enum "neighbor reset" {
				value 7;
				description "neighbor reset";
			}
			enum "interface status changed" {
				value 8;
				description "interface status changed";
			}
			enum "graceful restart unconfigured at process level" {
				value 9;
				description "graceful restart unconfigured at pro"
+ "cess level";
			}
			enum "grace lsa not found" {
				value 10;
				description "grace lsa not found";
			}
		}
		description "";
	}
	typedef ospfv2HelperExtReason {
		type enumeration {
			enum "none" {
				value 0;
				description "none";
			}
			enum "inProgress" {
				value 1;
				description "inProgress";
			}
			enum "completed" {
				value 2;
				description "completed";
			}
			enum "timedOut" {
				value 3;
				description "timedOut";
			}
			enum "topologyChanged" {
				value 4;
				description "topologyChanged";
			}
		}
		description "";
	}
	typedef ospfv2NbrGRHelperStat {
		type enumeration {
			enum "helping" {
				value 0;
				description "helping";
			}
			enum "notHelping" {
				value 1;
				description "notHelping";
			}
		}
		description "";
	}
	typedef ospfv2IfRowStatus {
		type enumeration {
			enum "none" {
				value 0;
				description "none";
			}
			enum "active" {
				value 1;
				description "active";
			}
			enum "notInService" {
				value 2;
				description "notInService";
			}
			enum "notReady" {
				value 3;
				description "notReady";
			}
			enum "createAndGo" {
				value 4;
				description "createAndGo";
			}
			enum "createAndWait" {
				value 5;
				description "createAndWait";
			}
			enum "destroy" {
				value 6;
				description "destroy";
			}
		}
		description "";
	}
	typedef oteLinkType {
		type enumeration {
			enum "None" {
				value 0;
				description "None:";
			}
			enum "P2P" {
				value 1;
				description "P2P:";
			}
			enum "Multi-access" {
				value 2;
				description "Multi-access:";
			}
		}
		description "";
	}
	typedef ospfv2commDCNIntfType {
		type enumeration {
			enum "DCC" {
				value 0;
				description "All DCN physical interface:";
			}
		}
		description "";
	}
	typedef ospfv2commProcDcnAuthenMode {
		type enumeration {
			enum "none" {
				value 0;
				description "none:";
			}
			enum "md5" {
				value 1;
				description "md5:";
			}
			enum "hmac-sha256" {
				value 2;
				description "hmac-sha256";
			}
			enum "hmac-md5" {
				value 3;
				description "hmac-md5:";
			}
			enum "simple" {
				value 4;
				description "simple:";
			}
		}
		description "";
	}
	typedef ospfPeerIpIgnoreType {
		type enumeration {
			enum "Disable" {
				value 0;
				description "Disable:";
			}
			enum "Enable" {
				value 1;
				description "Enable:";
			}
		}
		description "";
	}
	typedef ospfBfdDiagInfoType {
		type enumeration {
			enum "No diagnostic information" {
				value 0;
				description "No diagnostic information";
			}
			enum "Control Detection Time Expired" {
				value 1;
				description "Control Detection Time Expired";
			}
			enum "Echo Function Failed" {
				value 2;
				description "Echo Function Failed";
			}
			enum "Neighbor is down" {
				value 3;
				description "Neighbor is down";
			}
			enum "Forwarding Plane Reset" {
				value 4;
				description "Forwarding Plane Reset";
			}
			enum "Path Down" {
				value 5;
				description "Path Down";
			}
			enum "Concatenated Path Down" {
				value 6;
				description "Concatenated Path Down";
			}
			enum "Administator down" {
				value 7;
				description "Administator down";
			}
			enum "Reverse Concatenated Path Down" {
				value 8;
				description "Reverse Concatenated Path Down";
			}
			enum "administrator down event received" {
				value 9;
				description "administrator down event received";
			}
			enum "Global BFD is not enabled" {
				value 10;
				description "Global BFD is not enabled";
			}
			enum "BFD session number reaches the max" {
				value 11;
				description "BFD session number reaches the max";
			}
		}
		description "";
	}
}
