/*
WARNING:
This yang model is just for fuction ONOS opensource project demo purpose only,
And is subject to change in future, Huawei does not commit provide compatibilty
in commercial product.
*/
module huawei-ac-ne-pub-type {
    namespace "urn:huawei:yang:huawei-ac-ne-pub-type";
    prefix "pub-type";
    
    organization "Huawei Technologies Co.,Ltd.";
    contact "Huawei Industrial Base Bantian, Longgang Shenzhen 518129                    
              People's Republic of China                    
              Website: http://www.huawei.com Email: support@huawei.com";
    description "pub-type";
    revision "2016-01-05";
    typedef editOperationType {
        type enumeration {
            enum "merge" {
                value 0;
                description "";
            }
            enum "replace" {
                value 1;
                description "";
            }
            enum "create" {
                value 2;
                description "";
            }
            enum "delete" {
                value 3;
                description "";
            }
        }
    }
    typedef timeZone {
        description "timeZone is like +08:00";
        type string {
            length "0..15";
        }
    }
    typedef time_hhmm {
        description "time_hhmm is like string";
        type string {
            length "5";
            pattern "((^([0-1][0-9]|2[0-3])):([0-5][0-9])$)";
        }
    }
    typedef macAddress {
        description "A MAC address in standard notation";
        type string {
            length "0..255";
        }
    }
    typedef ipv4Address {
        description "An IPV4 address in dotted decimal notation";
        type string {
            length "0..255";
            pattern "((([1-9]?[0-9]|1[0-9][0-9]|2[0-4][0-9]|25[0-5])\.){3}([1-9]?[0-9]|1[0-9][0-9]|2[0-4][0-9]|25[0-5]))";
        }
    }
    typedef ipv6Address {
        description "An IPV6 address in standard notation";
        type string {
            length "0..255";
        }
    }
    typedef ipv4PrefixLength {
        description "An IPv4 address prefix length. Must lie between 0 and 32 inclusive.";
        type uint32 {
            range "0..32";
        }
    }
    typedef ipv6PrefixLength {
        description "An IPv6 address prefix length. Must lie between 0 and 128 inclusive.";
        type uint32 {
            range "0..128";
        }
    }
    typedef ipv4AddressPrefix {
        description "now ipv4AddressPrefix is like string";
        type string {
            length "0..255";
        }
    }
    typedef ipv6AddressPrefix {
        description "now ipv6AddressPrefix is like string";
        type string {
            length "0..255";
        }
    }
    typedef block {
        description "now block is like string";
        type string {
            length "0..255";
        }
    }
    typedef oid {
        description "now oid is like string";
        type string {
            length "0..255";
        }
    }
    typedef data {
        description "now data is like string";
        type string {
            length "0..255";
        }
    }
    typedef chassisPath {
        description "chassisPath is an unsignedInt";
        type uint32 {
            range "0..127";
        }
    }
    typedef slotPath {
        description "slotPath is like 1/1";
        type string {
            length "1..127";
            pattern "\d+/\d+";
        }
    }
    typedef cardPath {
        type string {
            length "1..127";
        }
    }
    typedef ifNameString {
        description "ifName is like ethernet1/1/1/1";
        type string {
            length "1..63";
        }
    }
    typedef ifName {
        type ifNameString;
    }
    typedef vrfNameExt {
        type vrfName;
    }
    typedef positionString {
        description "board position is like [1], serialPort position is like[1/1/1/1:2:3]";
        type string {
            length "1..32";
        }
    }
    typedef position {
        type positionString;
    }
    typedef password {
        description "now password is like string";
        type string {
            length "1..16";
        }
    }
    typedef passwordOSPF {
        description "now password is like string";
        type string {
            length "1..8";
        }
    }
    typedef passwordExtend {
        description "now passwordExtend is like string";
        type string {
            length "1..255";
        }
    }
    typedef oneInputPasswordExtend {
        description "now oneInputPasswordExtend is like string, only input once no need to confirm";
        type string {
            length "1..255";
        }
    }
    typedef mibString {
        description "now mibString is like string";
        type string {
            length "0..255";
        }
    }
    typedef vrfName {
        description "now vrfName is like string";
        type string {
            length "1..31";
        }
    }
    typedef keyChainName {
        description "now keyChainName is like string";
        type string {
            length "0..47";
        }
    }
    typedef ipAddress {
        description "ipAddress support both IPV4 and IPV6";
        type string {
            length "0..255";
        }
    }
    typedef ipv4Mask {
        description "ipv4Mask support both mask and length format";
        type string {
            length "0..255";
        }
    }
    typedef ipv6Mask {
        description "ipv6Mask support both mask and length format";
        type string {
            length "0..255";
        }
    }
    typedef timeTick {
        description "timeTick is like unsignedInt";
        type uint32;
    }
    typedef identifierString {
        description "now identifierString is like string, which is used for identifier with strict limitation";
        type string {
            pattern "([^\s?|>]*)";
        }
    }
    typedef descriptionString {
        description "now descriptionString is like string, which is used for description with little limitation";
        type string {
            pattern "([^?]*)";
        }
    }
    typedef rowStatus {
        type enumeration {
            enum "active" {
                value 0;
                description "active:";
            }
            enum "notInService" {
                value 1;
                description "notInService:";
            }
            enum "notReady" {
                value 2;
                description "notReady:";
            }
        }
        description "rowStatus is like string";
    }
    typedef bits8 {
        description "bits8 is like unsignedByte";
        type uint8;
    }
    typedef bits16 {
        description "bits16 is like unsignedShort";
        type uint16;
    }
    typedef bits32 {
        description "bits32 is like unsignedInt";
        type uint32;
    }
    typedef bits64 {
        description "bits64 is like unsignedLong";
        type uint64;
    }
    typedef percent {
        description "percent is like unsignedByte";
        type uint8 {
            range "0..100";
        }
    }
    typedef VLAN_BITMAP {
        description "vlan bitmap";
        type string {
            length "2049";
        }
    }
    typedef bitMap {
        description "bitMap";
        type string {
            length "1..65535";
        }
    }
    typedef bandWidth {
        description "Type of ifOperSpeed";
        type uint64;
    }
    typedef appType {
        type enumeration {
            enum "lct" {
                value 0;
                description "";
            }
            enum "ems" {
                value 1;
                description "";
            }
            enum "cmd" {
                value 2;
                description "";
            }
            enum "ftp" {
                value 3;
                description "";
            }
            enum "unknown" {
                value 4;
                description "";
            }
        }
        description "";
    }
    typedef teTnlName {
        description "TE tunnel name";
        type string {
            length "1..35";
            pattern "^[^ ]*$";
        }
    }
    typedef teTnlNameExt {
        type teTnlName;
    }
    typedef devmTimeslotListType {
        description "";
        type string {
            length "1..61";
        }
    }
    typedef hexBinary {
        description "This is a hexadecimal variable.";
        type string {
            length "1..10";
            pattern "(0x|0X)?[0-9a-fA-F]+";
        }
    }
    typedef date {
        description "XSD date string type.";
        type string {
            pattern "\d{4}-\d{2}-\d{2}";
        }
        reference "http://www.w3.org/TR/2004/REC-xmlschema-2-20041028/datatypes.html#date";
    }
    typedef time {
        description "XSD time string type.";
        type string {
            pattern "\d{2}:\d{2}:\d{2}";
        }
        reference "http://www.w3.org/TR/2004/REC-xmlschema-2-20041028/datatypes.html#date";
    }
    typedef data-src-type {
        type enumeration {
            enum ecs {
                value 0;
                description "The data is from single device configuration.";
                       }
            enum e2e {
                value 1;
                description "The data is from E2E configuration.";
                       }
            enum sync {
                value 2;
                description "The data is synchronized from the southbound configuration.";
                       }
         }
     }
}
