/*
WARNING:
This yang model is just for fuction ONOS opensource project demo purpose only,
And is subject to change in future, Huawei does not commit provide compatibilty
in commercial product.
*/
submodule huawei-ac-ne-ne-ifm-hdlc {
    belongs-to "huawei-ac-ne-ne-ifm" {
        prefix "ifm";
    }
    import huawei-ac-ne-pub-type {
        prefix "pub-type";
    }
    include huawei-ac-ne-ne-ifm-pppbase;
    
    organization "Huawei Technologies Co.,Ltd.";
    contact "Huawei Industrial Base Bantian, Longgang Shenzhen 518129                    
              People's Republic of China                    
              Website: http://www.huawei.com Email: support@huawei.com";
    description "ifm-pppbase";
    revision "2013-01-01";
    grouping hdlc_chdlc_oper_hdlcConfig_type {
        description "";
        leaf downWhenLoop {
            type boolean;
            default "false";
            description "";
        }
        container ifLink {
            uses ifm:ifm_pppbase_ifLink_type;
        }
    }
}
