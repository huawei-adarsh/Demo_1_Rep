/*
WARNING:
This yang model is just for fuction ONOS opensource project demo purpose only,
And is subject to change in future, Huawei does not commit provide compatibilty
in commercial product.
*/
submodule huawei-ac-ne-ne-ifm-fr {
    belongs-to "huawei-ac-ne-ne-ifm" {
        prefix "ifm";
    }
    import huawei-ac-ne-pub-type {
        prefix "pub-type";
    }
    include huawei-ac-ne-ne-ifm-fr-type;
    include huawei-ac-ne-ne-ifm-pppbase;
    
    organization "Huawei Technologies Co.,Ltd.";
    contact "Huawei Industrial Base Bantian, Longgang Shenzhen 518129                    
              People's Republic of China                    
              Website: http://www.huawei.com Email: support@huawei.com";
    description "ifm-pppbase";
    revision "2013-01-01";
    grouping ifm_frConfig_type {
        description "";
        leaf lmiType {
            type cfgLmiType;
            default "ansi";
            description "";
        }
        leaf ifType {
            type cfgRole;
            default "dte";
            description "";
        }
        leaf n391dte {
            type uint32 {
                range "1..255";
            }
            default "6";
            description "";
        }
        leaf n392dce {
            type uint64 {
                range "1..10";
            }
            default "3";
            description "";
        }
        leaf n392dte {
            type uint64 {
                range "1..10";
            }
            default "4";
            description "";
        }
        leaf n393dce {
            type uint64 {
                range "1..10";
            }
            default "4";
            description "";
        }
        leaf n393dte {
            type uint32 {
                range "1..10";
            }
            default "4";
            description "";
        }
        leaf t392dce {
            type uint64 {
                range "5..30";
            }
            default "15";
            description "";
        }
        container dlcis {
            leaf dlci {
                type uint32 {
                    range "16..1007";
                }
                description "";
            }
        }
        container ifLink {
            uses ifm:ifm_pppbase_ifLink_type;
        }
    }
}
