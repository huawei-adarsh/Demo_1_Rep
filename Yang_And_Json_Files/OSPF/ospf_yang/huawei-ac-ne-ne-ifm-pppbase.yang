/*
WARNING:
This yang model is just for fuction ONOS opensource project demo purpose only,
And is subject to change in future, Huawei does not commit provide compatibilty
in commercial product.
*/
submodule huawei-ac-ne-ne-ifm-pppbase {
    belongs-to "huawei-ac-ne-ne-ifm" {
        prefix "ifm";
    }
    import huawei-ac-ne-pub-type {
        prefix "pub-type";
    }
    include huawei-ac-ne-ne-ifm-pppbase-type;
    
    organization "Huawei Technologies Co.,Ltd.";
    contact "Huawei Industrial Base Bantian, Longgang Shenzhen 518129                    
              People's Republic of China                    
              Website: http://www.huawei.com Email: support@huawei.com";
    description "ifm-pppbase-type";
    revision "2013-01-01";
	grouping ifm_pppbase_pppConfig_type_cfg {
        description "";
        leaf negoTimeout {
            type uint32 {
                range "1..10";
            }
            default "3";
            description "";
        }
        leaf deadLinkTime {
            type uint32 {
                range "5..30";
            }
            default "30";
            description "";
        }
        leaf peerIpAddr {
            type pub-type:ipv4Address;
            description "";
        }
        leaf mruNegoMtd {
            type pppbaseMruNegoMtd;
            default "IPV4";
            description "";
        }
        leaf ifPapAuth {
            type boolean;
            default "false";
            description "";
        }
        leaf ifChapAuth {
            type boolean;
            default "false";
            description "";
        }
        leaf magicNumCheck {
            type boolean;
            default "false";
            description "";
        }
        leaf osicpNego {
            type pppbaseNcpNegoType;
            default "Enable";
            description "";
        }
        leaf mplscpNego {
            type pppbaseNcpNegoType;
            default "Enable";
            description "";
        }
        leaf peerHostRoute {
            type boolean;
            default "false";
            description "";
        }
        leaf papUserName {
            type string {
                length "1..253";
            }
            description "";
        }
        leaf papPaswrd {
            type pub-type:password;
            description "";
        }
        leaf chapUserName {
            type string {
                length "1..253";
            }
            description "";
        }
        leaf chapPaswrd {
            type pub-type:password;
            description "";
        }
        leaf dnsAdmitAny {
            type boolean;
            description "";
        }
        leaf primDNSAddr {
            type pub-type:ipv4Address;
            description "";
        }
        leaf secndDNSAddr {
            type pub-type:ipv4Address;
            description "";
        }
        container ifLink {
            leaf timeInternal {
                type uint32 {
                    range "0..32767";
                }
                default "10";
                description "";
            }
        }
        container crcParam {
            description "";
            leaf errType {
                type pppbaseCrcType;
                default "Default";
                description "";
            }
            leaf highThreshold {
                type uint32 {
                    range "1..4294967295";
                }
                description "";
            }
            leaf lowThreshold {
                type uint32 {
                    range "1..4294967295";
                }
                description "";
            }
            leaf interval {
                type uint32 {
                    range "1..65535";
                }
                description "";
            }
            leaf pktAlaCof {
                type uint32 {
                    range "1..9";
                }
                description "";
            }
            leaf pktAlaPow {
                type uint32 {
                    range "1..5";
                }
                description "";
            }
            leaf pktResCof {
                type uint32 {
                    range "1..9";
                }
                description "";
            }
            leaf pktResPow {
                type uint32 {
                    range "1..6";
                }
                description "";
            }
            leaf bitAlaCof {
                type string {
                    length "1";
                    pattern '^[1]';
                }
                description "";
            }
            leaf bitAlaPow {
                type uint32 {
                    range "3..6";
                }
                description "";
            }
            leaf bitResCof {
                type string {
                    length "1";
                    pattern '^[1]';
                }
                description "";
            }
            leaf bitResPow {
                type uint32 {
                    range "3..6";
                }
                description "";
            }
            leaf shutdown {
                type boolean;
                description "";
            }
            leaf crcBit {
                type pppbaseCrcBitType;
                default "32";
                description "";
            }
            leaf sampleFactor {
                type uint32 {
                    range "10..100";
                }
                default "50";
                description "";
            }
            leaf childMaxNum {
                type uint32 {
                    range "10..100";
                }
                default "50";
                description "";
            }
            leaf childAlarmNum {
                type uint32 {
                    range "1..100";
                }
                default "5";
                description "";
            }
            leaf childResmNum {
                type uint32 {
                    range "1..100";
                }
                default "30";
                description "";
            }
        }
    }
    grouping ifm_pppbase_pppConfig_type_oper {
        description "";
        leaf negoTimeout {
            type uint32 {
                range "1..10";
            }
            config false;
            default "3";
            description "";
        }
        leaf deadLinkTime {
            type uint32 {
                range "5..30";
            }
            config false;
            default "30";
            description "";
        }
        leaf peerIpAddr {
            type pub-type:ipv4Address;
            config false;
            description "";
        }
        leaf mruNegoMtd {
            type pppbaseMruNegoMtd;
            config false;
            default "IPV4";
            description "";
        }
        leaf ifPapAuth {
            type boolean;
            config false;
            default "false";
            description "";
        }
        leaf ifChapAuth {
            type boolean;
            config false;
            default "false";
            description "";
        }
        leaf magicNumCheck {
            type boolean;
            config false;
            default "false";
            description "";
        }
        leaf osicpNego {
            type pppbaseNcpNegoType;
            config false;
            default "Enable";
            description "";
        }
        leaf mplscpNego {
            type pppbaseNcpNegoType;
            default "Enable";
            description "";
        }
        leaf peerHostRoute {
            type boolean;
            config false;
            default "false";
            description "";
        }
        leaf papUserName {
            type string {
                length "1..253";
            }
            config false;
            description "";
        }
        leaf papPaswrd {
            type pub-type:password;
            config false;
            description "";
        }
        leaf chapUserName {
            type string {
                length "1..253";
            }
            config false;
            description "";
        }
        leaf chapPaswrd {
            type pub-type:password;
            config false;
            description "";
        }
        leaf dnsAdmitAny {
            type boolean;
            config false;
            description "";
        }
        leaf primDNSAddr {
            type pub-type:ipv4Address;
            config false;
            description "";
        }
        leaf secndDNSAddr {
            type pub-type:ipv4Address;
            config false;
            description "";
        }
        container ifLink {
            leaf timeInternal {
                type uint32 {
                    range "0..32767";
                }
                config false;
                default "10";
                description "";
            }
        }
        container crcParam {
            description "";
            leaf errType {
                type pppbaseCrcType;
                config false;
                default "Default";
                description "";
            }
            leaf highThreshold {
                type uint32 {
                    range "1..4294967295";
                }
                config false;
                description "";
            }
            leaf lowThreshold {
                type uint32 {
                    range "1..4294967295";
                }
                config false;
                description "";
            }
            leaf interval {
                type uint32 {
                    range "1..65535";
                }
                config false;
                description "";
            }
            leaf pktAlaCof {
                type uint32 {
                    range "1..9";
                }
                config false;
                description "";
            }
            leaf pktAlaPow {
                type uint32 {
                    range "1..5";
                }
                config false;
                description "";
            }
            leaf pktResCof {
                type uint32 {
                    range "1..9";
                }
                config false;
                description "";
            }
            leaf pktResPow {
                type uint32 {
                    range "1..6";
                }
                config false;
                description "";
            }
            leaf bitAlaCof {
                type string {
                    length "1";
                    pattern '^[1]';
                }
                config false;
                description "";
            }
            leaf bitAlaPow {
                type uint32 {
                    range "3..6";
                }
                config false;
                description "";
            }
            leaf bitResCof {
                type string {
                    length "1";
                    pattern '^[1]';
                }
                config false;
                description "";
            }
            leaf bitResPow {
                type uint32 {
                    range "3..6";
                }
                config false;
                description "";
            }
            leaf shutdown {
                type boolean;
                config false;
                description "";
            }
            leaf crcBit {
                type pppbaseCrcBitType;
                config false;
                default "32";
                description "";
            }
            leaf sampleFactor {
                type uint32 {
                    range "10..100";
                }
                config false;
                default "50";
                description "";
            }
            leaf childMaxNum {
                type uint32 {
                    range "10..100";
                }
                config false;
                default "50";
                description "";
            }
            leaf childAlarmNum {
                type uint32 {
                    range "1..100";
                }
                config false;
                default "5";
                description "";
            }
            leaf childResmNum {
                type uint32 {
                    range "1..100";
                }
                config false;
                default "30";
                description "";
            }
        }
        container pppStatistics {
            leaf inputShortPkts {
                type uint32;
                config false;
                default "0";
                description "";
            }
            leaf inputLongPkts {
                type uint32;
                config false;
                default "0";
                description "";
            }
            leaf inputCrcPkts {
                type uint32;
                config false;
                default "0";
                description "";
            }
            leaf inputLostPkts {
                type uint32;
                config false;
                default "0";
                description "";
            }
            leaf outLostPkts {
                type uint32;
                config false;
                default "0";
                description "";
            }
            leaf outOverPkts {
                type uint32;
                config false;
                default "0";
                description "";
            }
            leaf outUnderPkts {
                type uint32;
                config false;
                default "0";
                description "";
            }
        }
    }
    grouping ifm_pppbase_ifLink_type {
        description "";
        leaf timeInternal {
            type uint32 {
                range "0..32767";
            }
            default "10";
            description "";
        }
    }
}
