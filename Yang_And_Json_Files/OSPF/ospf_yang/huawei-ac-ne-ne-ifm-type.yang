/*
WARNING:
This yang model is just for fuction ONOS opensource project demo purpose only,
And is subject to change in future, Huawei does not commit provide compatibilty
in commercial product.
*/
/******************************************************
 * Copyright (C) 2015-2016 Huawei Technologies Co., Ltd. All rights reserved.
 * Module description & tree structure
 ***************************************************/
submodule huawei-ac-ne-ne-ifm-type {
    belongs-to huawei-ac-ne-ne-ifm {
        prefix "ifm";
    }
    
    organization "Huawei Technologies Co.,Ltd.";
    contact 
	"Huawei Industrial Base
	 Bantian, Longgang
	 Shenzhen 518129
	 People's Republic of China
	 Website: http://www.huawei.com
	 Email: support@huawei.com";
	revision "2016-03-23" {
	    description "Initial Version";
    }
	
    typedef ifmcommPhyType {
        description "ifmcommRouterType is like Ethernet/Eth-Trunk/...";
        type enumeration {
            enum "Ethernet" {
                value 0;
                description "Ethernet interface.";
            }
            enum "GigabitEthernet" {
                value 1;
                description "GigabitEthernet interface.";
            }
            enum "Eth-Trunk" {
                value 2;
                description "Eth-Trunk interface.";
            }
            enum "Ip-Trunk" {
                value 3;
                description "IP-Trunk interface.";
            }
            enum "Pos" {
                value 4;
                description "POS interface.";
            }
            enum "Tunnel" {
                value 5;
                description "Tunnel interface.";
            }
            enum "NULL" {
                value 6;
                description "Null interface.";
            }
            enum "LoopBack" {
                value 7;
                description "Loopback interface.";
            }
            enum "Vlanif" {
                value 8;
                description "VLANIF interface.";
            }
            enum "100GE" {
                value 9;
                description "100 GigabitEthernet interface.";
            }
            enum "40GE" {
                value 10;
                description "40 GigabitEthernet interface.";
            }
            enum "MTunnel" {
                value 11;
                description "MTunnel interface.";
            }
            enum "10GE" {
                value 12;
                description "10 GigabitEthernet interface.";
            }
            enum "GEBrief" {
                value 13;
                description "GigabitEthernet interface.";
            }
            enum "MEth" {
                value 14;
                description "Management Ethernet interface.";
            }
            enum "Stack-Port" {
                value 15;
                description "Stack-port interface.";
            }
            enum "Sip" {
                value 16;
                description "System interconnect port.";
            }
            enum "Cpos" {
                value 17;
                description "CPOS controller.";
            }
            enum "E1" {
                value 18;
                description "E1 controller.";
            }
            enum "Serial" {
                value 19;
                description "Serial interface.";
            }
            enum "Mp-group" {
                value 20;
                description "MP-group interface.";
            }
            enum "Virtual-Ethernet" {
                value 21;
                description "Virtual-Ethernet interface.";
            }
            enum "VMEth" {
                value 22;
                description "Virtual management Ethernet interface.";
            }
            enum "Ima-group" {
                value 23;
                description "IMA-group interface.";
            }
            enum "Remote-Ap" {
                value 24;
                description "Virtual cluster access remote access point interface.";
            }
            enum "VBridge" {
                value 25;
                description "Virtual cluster access bridge interface.";
            }
            enum "Atm-Bundle" {
                value 26;
                description "ATM-Bundle interface.";
            }
            enum "Fiber-Channel" {
                value 27;
                description "Fiber-Channel interface.";
            }
            enum "Infiniband" {
                value 28;
                description "Infiniband interface.";
            }
            enum "Lmpif" {
                value 29;
                description "Lmpif interface.";
            }
            enum "T1" {
                value 30;
                description "T1 controller.";
            }
            enum "T3" {
                value 31;
                description "T3 controller.";
            }
            enum "Global-VE" {
                value 32;
                description "Global-VE interface.";
            }
            enum "VC4" {
                value 33;
                description "VC4 interface.";
            }
            enum "VC12" {
                value 34;
                description "VC12 interface.";
            }
            enum "Vbdif" {
                value 35;
                description "VBDIF interface.";
            }
            enum "Fabric-Port" {
                value 36;
                description "Fabric-Port interface.";
            }
            enum "E3" {
                value 37;
                description "E3 controller.";
            }
            enum "Otn" {
                value 38;
                description "OTN controller.";
            }
            enum "Vp" {
                value 39;
                description "VP interface.";
            }
            enum "DcnInterface" {
                value 40;
                description "DCN interface.";
            }
            enum "Cpos-Trunk" {
                value 41;
                description "Cpos-Trunk interface.";
            }
            enum "Pos-Trunk" {
                value 42;
                description "Pos-Trunk interface.";
            }
            enum "Trunk-Serial" {
                value 43;
                description "Trunk-Serial interface.";
            }
            enum "Global-Ima-Group" {
                value 44;
                description "Global-Ima-Group interface.";
            }
            enum "Global-Mp-Group" {
                value 45;
                description "Global-Mp-Group interface.";
            }
            enum "Gmpls-Uni" {
                value 46;
                description "Gmpls-Uni interface.";
            }
            enum "Wdm" {
                value 47;
                description "Wdm controller.";
            }
            enum "Nve" {
                value 48;
                description "NVE interface.";
            }
            enum "FCoE-Port" {
                value 49;
                description "FCoE-Port Interface.";
            }
            enum "Virtual-Template" {
                value 50;
                description "Virtual-Template Interface.";
            }
            enum "FC" {
                value 51;
                description "FC Interface.";
            }
            enum "4x10GE" {
                value 52;
                description "4x10 GigabitEthernet interface.";
            }
            enum "10x10GE" {
                value 53;
                description "10x10 GigabitEthernet interface.";
            }
            enum "3x40GE" {
                value 54;
                description "3x40 GigabitEthernet interface.";
            }
            enum "4x25GE" {
                value 55;
                description "4x25 GigabitEthernet interface.";
            }
            enum "25GE" {
                value 56;
                description "25 GigabitEthernet interface.";
            }
        }
    }
    typedef ifmcommRouterType {
        description "ifmcommRouterType is like NBMA/Broadcast/...";
        type enumeration {
            enum "PtoP" {
                value 0;
                description "Point to point.";
            }
            enum "PtoMP" {
                value 1;
                description "Point to multi-point.";
            }
            enum "Broadcast" {
                value 2;
                description "Broadcast.";
            }
            enum "NBMA" {
                value 3;
                description "Non-broadcast multi-access.";
            }
            enum "invalid" {
                value 4;
                description "None.";
            }
        }
    }
    typedef ifmcommAdminStaType {
        description "ifmcommAdminStaType is like up/down";
        type enumeration {
            enum "up" {
                value 0;
                description "Administratively Up.";
            }
            enum "down" {
                value 1;
                description "Administratively Down.";
            }
        }
    }
    typedef ifmcommNetWorkLayerState {
        description "ifmcommAdminStaType is like up/down";
        type enumeration {
            enum "ipv4andipv6up" {
                value 0;
                description "ready to pass packets:";
            }
            enum "ipv4andipv6down" {
                value 1;
                description "not ready to pass packets:";
            }
        }
    }
    typedef ifmcommLinkProtocol {
        description "ifmcommLinkProtocol is like ppp/hdlc/fr";
        type enumeration {
            enum "ethernet" {
                value 0;
                description "The link protocol of the interface is Ethernet.";
            }
            enum "ppp" {
                value 1;
                description "The link protocol of the interface is PPP.";
            }
            enum "hdlc" {
                value 2;
                description "The link protocol of the interface is HDLC.";
            }
            enum "fr" {
                value 3;
                description "The link protocol of the interface is FR.";
            }
            enum "tdm" {
                value 4;
                description "The link protocol of the interface is TDM.";
            }
            enum "atm" {
                value 5;
                description "The link protocol of the interface is ATM.";
            }
            enum "invalid" {
                value 6;
                description "None.";
            }
        }
    }
    typedef ifmcommIfStatus {
        description "ifmcommIfStatus is like up/down";
        type enumeration {
            enum "up" {
                value 0;
                description "The interface is in Up state.";
            }
            enum "down" {
                value 1;
                description "The interface is in Down state.";
            }
        }
    }
    typedef ifmam4IpAddrType {
        description "ifmam4IpAddrType is like main/sub";
        type enumeration {
            enum "main" {
                value 0;
                description "Primary address of an interface.";
            }
            enum "sub" {
                value 1;
                description "Secondary address of an interface.";
            }
            enum "neg" {
                value 2;
                description "Negotiated address of an interface.";
            }
            enum "neg_remote" {
                value 3;
                description "Remotely negotiated address of an interface.";
            }
            enum "unnumber" {
                value 4;
                description "Unnumbered address of an interface.";
            }
            enum "nap" {
                value 5;
                description "Negotiated address using the Neighbor access protocol.";
            }
        }
    }
    typedef ifmam4CfgType {
        description "ifmam4CfgType is like config/unnumbered/negotiation";
        type enumeration {
            enum "config" {
                value 0;
                description "Configured address.";
            }
            enum "negotiation" {
                value 1;
                description "Negotiated address.";
            }
            enum "unnumbered" {
                value 2;
                description "Unnumbered address.";
            }
        }
    }
    typedef ifmam4IpAddrCreateOrDelete {
        description "ifmam4IpAddrCreateOrDelete is like Config/Delete";
        type enumeration {
            enum "Config" {
                value 0;
                description "The IP address is manually configured.";
            }
            enum "Delete" {
                value 1;
                description "No IP address is allocated.";
            }
        }
    }
    typedef ifmam6IpAddr6Type {
        description "ifmam6IpAddr6Type is like linklocal/global/ndPrefix";
        type enumeration {
            enum "global" {
                value 0;
                description "Global unicast address.";
            }
            enum "linkLocal" {
                value 1;
                description "Link local address.";
            }
            enum "ndPrefix" {
                value 2;
                description "ND prefix.";
            }
            enum "eui64" {
                value 3;
                description "EUI 64.";
            }
            enum "anycast" {
                value 4;
                description "Anycast address.";
            }
        }
    }
    typedef ifmam6IDGenType {
        description "ifmam6IDGenType is like none/cga/eui64";
        type enumeration {
            enum "none" {
                value 0;
                description "none.";
            }
            enum "cga" {
                value 1;
                description "CGA.";
            }
            enum "eui64" {
                value 2;
                description "EUI 64.";
            }
        }
    }
    typedef ifmcommServiceType {
        description "ifmcommServiceType is like manageport/trunkmember/l2ser/l3ser/l2switch";
        type enumeration {
            enum "None" {
                value 0;
                description "None.";
            }
            enum "TrunkMember" {
                value 1;
                description "Trunk member.";
            }
            enum "StackMember" {
                value 2;
                description "Stack member.";
            }
            enum "MpMember" {
                value 3;
                description "MP-Group Member.";
            }
            enum "VbridgeMember" {
                value 4;
                description "VBridge member.";
            }
            enum "ImaMember" {
                value 5;
                description "IMA member.";
            }
            enum "BundleMember" {
                value 6;
                description "Bundle member.";
            }
            enum "FabricMember" {
                value 7;
                description "Fabric member";
            }
            enum "LagMasterMember" {
                value 8;
                description "Master member in a LAG.";
            }
            enum "LagSlaveMember" {
                value 9;
                description "Slave member in a LAG.";
            }
            enum "CposTrunkMember" {
                value 10;
                description "Cpos-Trunk Member.";
            }
            enum "PosTrunkMember" {
                value 11;
                description "Pos-Trunk Member.";
            }
            enum "GlobalMpMember" {
                value 12;
                description "Global-Mp-group Member.";
            }
            enum "GlobalImaMember" {
                value 13;
                description "Global-Ima-group Member.";
            }
        }
    }
    typedef ifmcommErrorDownType {
        description "ifmcommErrorDownType is like bpdu-protection";
        type enumeration {
            enum "bpdu-protection" {
                value 0;
                description "BPDU protection.";
            }
            enum "auto-defend" {
                value 1;
                description "Attack source tracing.";
            }
            enum "monitor-link" {
                value 2;
                description "The uplink of monitor-link group is down.";
            }
            enum "loopback-detect" {
                value 3;
                description "Loopback detect.";
            }
            enum "portsec-reachedlimit" {
                value 4;
                description "Secure MAC addresses have reached the upper limit.";
            }
            enum "mac-address-flapping" {
                value 5;
                description "MAC address flapping.";
            }
            enum "storm-control" {
                value 6;
                description "Storm-control.";
            }
            enum "dual-active" {
                value 7;
                description "Dual-active.";
            }
            enum "no-stack-link" {
                value 8;
                description "No-stack-link.";
            }
            enum "crc-statistics" {
                value 9;
                description "CRC statistics.";
            }
            enum "transceiver-power-low" {
                value 10;
                description "The transceiver power is low.";
            }
            enum "link-flap" {
                value 11;
                description "Link flapping.";
            }
            enum "l2-loop-occured" {
                value 12;
                description "L2 loop.";
            }
            enum "stack-member-exceed-limit" {
                value 13;
                description "The number of stack members exceeds the limit.";
            }
            enum "spine-member-exceed-limit" {
                value 14;
                description "The number of spine members exceeds the limit.";
            }
            enum "leaf-mstp" {
                value 15;
                description "Leaf port mstp disable.";
            }
            enum "m-lag" {
                value 16;
                description "M-LAG peer detect error.";
            }
            enum "fabric-uplink-threshold" {
                value 17;
                description "Fabric uplink less then threshold.";
            }
            enum "stack-config-conflict" {
                value 18;
                description "Stack config conflict.";
            }
            enum "invalid" {
                value 19;
                description "None.";
            }
        }
    }
    typedef veInterfaceType {
        description "veIfType is like L2VE/L3VE";
        type enumeration {
            enum "L2VE" {
                value 0;
                description "Layer 2 Virtual-Ethernet interface.";
            }
            enum "L3VE" {
                value 1;
                description "Layer 3 Virtual-Ethernet interface.";
            }
            enum "invalid" {
                value 2;
                description "None.";
            }
        }
    }
    typedef veForwarModeType {
        description "veForwarMode is like through/loopback";
        type enumeration {
            enum "through" {
                value 0;
                description "Software loopback.";
            }
            enum "loopback" {
                value 1;
                description "Hardware loopback.";
            }
            enum "invalid" {
                value 2;
                description "None.";
            }
        }
    }
    typedef ifIpStatiModeType {
        description "fei statistic mode type";
        type enumeration {
            enum "forward" {
                value 0;
                description "Forward mode statistics.";
            }
            enum "mac" {
                value 1;
                description "MAC mode statistics.";
            }
            enum "invalid" {
                value 2;
                description "None.";
            }
        }
    }
    typedef ifmcommIfClassType {
        description "ifmcommIfClassType is like mainInterface/...";
        type enumeration {
            enum "mainInterface" {
                value 0;
                description "Main Interface.";
            }
            enum "subInterface" {
                value 1;
                description "Sub-interface.";
            }
        }
    }
    typedef ifmcommControlMtu {
        description "device Control Mtu/...";
        type enumeration {
            enum "1450" {
                value 0;
                description "1450.0";
            }
            enum "1500" {
                value 1;
                description "1500.0";
            }
        }
    }
    typedef ifmcommEncapType {
        description "fr encap type";
        type enumeration {
            enum "vlanType" {
                value 0;
                description "VLAN type.";
            }
            enum "dot1q" {
                value 1;
                description "Dot1q.";
            }
            enum "qinq" {
                value 2;
                description "QinQ.";
            }
            enum "p2p" {
                value 3;
                description "P2P.";
            }
            enum "p2mp" {
                value 4;
                description "P2MP.";
            }
            enum "l2ve" {
                value 5;
                description "L2VE.";
            }
            enum "l3ve" {
                value 6;
                description "L3VE.";
            }
            enum "vlanTypePolicy" {
                value 7;
                description "VLAN type policy.";
            }
            enum "dot1qPolicy" {
                value 8;
                description "Dot1q policy.";
            }
            enum "stackingPolicy" {
                value 9;
                description "Stacking policy.";
            }
            enum "untagPolicy" {
                value 10;
                description "Untag policy.";
            }
            enum "qinqMapping" {
                value 11;
                description "QinQ mapping.";
            }
            enum "l2vc" {
                value 12;
                description "L2VC.";
            }
            enum "l3vc" {
                value 13;
                description "L3VC.";
            }
            enum "evcUntag" {
                value 14;
                description "EvcUntag.";
            }
            enum "evcDot1q" {
                value 15;
                description "EvcDot1q.";
            }
            enum "evcQinq" {
                value 16;
                description "EvcQinq.";
            }
            enum "evcDefault" {
                value 17;
                description "EvcDefault.";
            }
            enum "evcDot1qPolicy" {
                value 18;
                description "EvcDot1qPolicy.";
            }
            enum "ietf" {
                value 19;
                description "IETF.";
            }
            enum "nonstandard" {
                value 20;
                description "Nonstandard.";
            }
            enum "userVlan" {
                value 21;
                description "userVlan";
            }
            enum "userVlanAny" {
                value 22;
                description "userVlan AnyOther";
            }
            enum "QinqLink" {
                value 23;
                description "QinqLink";
            }
            enum "invalid" {
                value 24;
                description "Invalid.";
            }
        }
    }
    typedef ifmcommStatMode {
        description "ifmcommStatMode is like baseInterface/baseVlanGroup";
        type enumeration {
            enum "baseInterface" {
                value 0;
                description "Statistics are collected based on interfaces.";
            }
            enum "baseVlanGroup" {
                value 1;
                description "Statistics are collected based on VLANs.";
            }
        }
    }
    typedef ifmcommPortMode {
        description "ifmcommPortMode is like L2/L3/MIX";
        type enumeration {
            enum "Mix" {
                value 0;
                description "Mix Port Mode";
            }
            enum "L2" {
                value 1;
                description "L2 Port Mode";
            }
            enum "L3" {
                value 2;
                description "L3 Port Mode";
            }
        }
    }
    typedef transAlarmDownType {
        description "transAlarmDownType is like enable/disable";
        type enumeration {
            enum "enable" {
                value 0;
                description "Enable Transmission-Alarm Down";
            }
            enum "disable" {
                value 1;
                description "Disable Transmission-Alarm Down";
            }
        }
    }
	typedef ifmcommDampLevelType {
		type enumeration {
			enum "light" {
				value 0;
				description "light:";
			}
			enum "middle" {
				value 1;
				description "middle:";
			}
			enum "heavy" {
				value 2;
				description "heavy:";
			}
			enum "manual" {
				value 3;
				description "manual:";
			}
		}
		description "ifmcommDampLevelType is light/middle/heavy/m"
+ "anual";
	}
}
