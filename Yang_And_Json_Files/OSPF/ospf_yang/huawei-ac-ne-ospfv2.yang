/*
WARNING:
This yang model is just for fuction ONOS opensource project demo purpose only,
And is subject to change in future, Huawei does not commit provide compatibilty
in commercial product.
*/
module huawei-ac-ne-ospfv2 {
	namespace "urn:huawei:yang:huawei-ac-ne-ospfv2";
	prefix ospfv2;
	import huawei-ac-nes {
		prefix inv; revision-date "2016-03-04";
	}
	    
	include huawei-ac-ne-ospfv2-ospfv2comm;
	include huawei-ac-ne-ospfv2-ospfv2comm-type;
	//TODO-ID-IS-NOT-READY type  include huawei-ac-ne-ospfv2-ospfv2comm-action;
	
	organization "Huawei Technologies Co., Ltd";
	contact 
	"Huawei Industrial Base
	 Bantian, Longgang
	 Shenzhen 518129
	 People's Republic of China
	 Website: http://www.huawei.com
	 Email: support@huawei.com
	";
	description "ne-ospfv2 yang";
	revision "2016-01-01" {
		reference "ne-ospfv2 yang";
	}
	augment "/inv:devices/inv:device/inv:inventory-cfg/inv:nes/inv:ne" {
	        //ext:augment-identifier "ospfCfgAug";
	        container ospfv2 {
					description "";
					container ospfv2comm {
						uses "ospf_ospfv2comm_ospfv2comm_cfg_type";
						description "";
					}
				}
	}
/*	augment "/inv:devices/inv:device/inv:inventory-oper/inv:nes/inv:ne" {
		container ospfv2-oper {
			description "";
			config "false";
			container ospfv2comm {
				uses "ospf_ospfv2comm_ospfv2comm_oper_type";
				description "";
			}
		}
	}*/
	
}
